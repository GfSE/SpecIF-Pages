# Project 'Related Terms'
- Rights: Creative Commons 4.0 CC BY-SA, https://creativecommons.org/licenses/by-sa/4.0/

## Vehicle (SpecIF:TermResourceClass)
- dcterms:description: Any means in or by which someone travels or something is carried or conveyed; a means of conveyance or transport. (Source: dictionary.com)

## Lorry (SpecIF:TermResourceClass)
- dcterms:description: Any of various conveyances running on rails, as for transporting material in a mine or factory. (Source: dictionary.com)

## Statements
- Lorry SysML:isSpecializationOf Vehicle
