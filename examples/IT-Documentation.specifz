# Example 'Integrated Process and IT Documentation' (2021-01-27)
This sample project illustrates the basic concepts of the modelling of business processes and IT, but is neither complete nor representative regarding the content.  The specification integrates and represents:• organisational view: organigram• business view:  business landscape and business data modell• application view: application landscape
- Rights: Creative Commons 4.0 CC BY-SA, https://creativecommons.org/licenses/by-sa/4.0/

## Project Information (SpecIF:Heading)
- dcterms:description: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
  This is a small show-case illustrating the basic concepts for documenting business processes and IT. In addition to the original text and diagrams you will find logical relations between the information elements. Most relations are derived automatically from the diagrams; the resulting semantic net lends itself for navigation, search and audit.
  The documentation represents and integrates:
  - Organisation perspective: [[Organization Chart]]
  - Business perspective: [[Business Landscape]] and Business Processes such as [[Process: Invoice Receipt Processing]]
  - Application perspective: [[Application Landscape]]
  - [[Requirements]]
  Integrating the perspectives means to (mostly automatically) tie a semantic net with relations:
  - Diagrams 'show' a model element, thus any element 'knows' on which diagrams it appears,
  - Components 'contain' sub-components,
  - Events 'trigger' activities,
  - Components 'satisfy' a requirement,
  - .. and many more.
  Active hyper-links make it easy to navigate along the relations. Insight is improved, navigation and audition are made more simple. For more information on the method applied, please refer to Specification Integration Facility (SpecIF), an initiative of the Gesellschaft für Systems Engineering (GfSE).
  If you are using Firefox, Chrome or Edge as a browser, don't hesitate to click on the diagram elements. It will bring you to the next level of detail.
  Stakeholders:
  | Name | Organisation | Telephone | Email |
  | --- | --- | --- | --- |
  | Dr. Oskar v. Dungern | enso managers gmbh |  | od@enso-managers.de |
  Legend:
  To distinguish their type, element names are preceded by one of the following symbols:
  | ▣ | Plan | A 'Diagram' is a graphical model view with a specific communication purpose, e.g. a business process or system composition. |
  | --- | --- | --- |
  | ■ | Actor (Role, Function) | An 'Actor' is a fundamental model element type representing an active entity, be it an activity, a process step, a function, a system component or a role. |
  | ● | State (Information) | A 'State' is a fundamental model element type representing a passive entity, be it a value, a condition, an information storage or even a physical shape. |
  | ⬧ | Event | An 'Event' is a fundamental model element type representing a time reference, a change in condition/value or more generally a synchronisation primitive. |
  | ✶ | Feature | A 'Feature' is an intentional distinguishing characteristic of a system, often a unique selling proposition. |
  | ↯ | Requirement | A 'Requirement' is a singular documented physical and functional need that a particular design, product or process must be able to perform. |

## About this Document (SpecIF:Heading)

## Specification Method (SpecIF:Heading)
- dcterms:description: This show-case applies the method called Fundamental Modelling Concept (FMC) as conceived by Prof. Siegfried Wendt and his collaborators. All plans (diagrams) are views of a common system engineering model. The plans share model elements. Thus, consistency is always maintained.
  The office and web documents are generated from the system engineering model. The ordering is in most projects (it can be rearranged, however, if appropriate):
  - All plans
  - Hierarchically ordered list of requirements
  - Alphabetically ordered glossary with descriptions of all model elements appearing on one or more plans
  - List of open issues.
  To read more on motivation and concepts of the specification method, please refer to: https://specif.de/files/resources/enso-m/documents-de/TdSE-2015_Dungern_Modellintegration-mit-fuenf-fundamentalen-Elementtypen_(Text).pdf.
  Further information on FMC can be found at:
  - http://www.f-m-c.org
  - Andreas Knöpfel, Bernhard Gröne, Peter Tabeling: Fundamental Modelling Concepts - Effective Communication of IT-Systems, Wiley & Sons, 2006

## Plan Types (SpecIF:Heading)
- dcterms:description: A 'Plan' is a model diagram, i.e. a view on the system model with a specific communication purpose. The following diagram types ("engineering plans") are used:
  - System composition (FMC block diagram) showing system modules and their interfaces
  - Business process models (BPMN) showing sequences of actions and events,
  - Dialog flows, life-cycle graphs or state transition diagrams (Petri-Net) showing behavior.

## Model Element Types (SpecIF:Heading)
- dcterms:description: The Fundamental Modelling Concept (FMC) deals with only 3 model element types 'Actor', 'State' and 'Event', whereas other methods such as SysML propose well over hundred different representations.
  - An 'Actor' is an active entity, be it an activity, a process step, a function, a system component or a role.
  - A 'State' is a passive entity, be it a value, a condition, an information storage or even a physical shape.
  - An 'Event' is a time reference, a change in condition/value or more generally a synchronisation primitive.
  - A 'Requirement' is a singular documented physical and functional need that a particular design, product or process must be able to perform.
  - A 'Feature' is an intentional distinguishing characteristic of a system, often a unique selling proposition.
  The model elements are connected with relations, most of which are automatically derived from the diagrams. For example, if a system component is drawn within another, a relationship 'contains' is created in the logic representation of the engineering model. Other relations, such as a system component 'satisfies' a requirement are created manually.
  Diagram
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
## Color Coding (SpecIF:Heading)
- dcterms:description: Diagram
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
## Benefits (SpecIF:Heading)
- dcterms:description:
  - Describe and visualize mechanic, electronic and software components in a common context.
  - Complementary, semantically integrated aspects of dynamic and static models, complemented by requirements and features per component result in higher quality and better understanding.
  - Some formal abstraction allows for systematic (and even semi-automatic) model checking.

## Business View (SpecIF:Heading)
- dcterms:description: In the beginning of this chapter, the organisational view is displayed. Subsequently, the business aspect is collected in addition to the documentation of the processes.

## Organization Chart (SpecIF:View)
- dcterms:description: The organigram shows the organisational structure of the company. Business functions of the [[business landscape]] are assigned to the particular organisational units in order to express the role the organisational unit plays in processes.
- SpecIF:Diagram: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

## Business Landscape (SpecIF:View)
- dcterms:description: The business landscape gives an overview over the business functions (often departments) and their interfaces, as well as the business objects which are exchanged at the interfaces. The business landscape shows the roles, functions and data from a conceptual, logical point of view. The mapping to concrete IT-systems follows in a later step.
  Click the elements on the diagram to navigate to their description.
- SpecIF:Diagram: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
- SpecIF:Notation: FMC Block Diagram

## Process: Invoice Receipt Processing (SpecIF:View)
- dcterms:description: This process describes the sequence of the automated editing of incoming [[Invoice]]s. After the invoice has reached the postal administration, it is scanned and delivered to the [[Invoice Management]] department. During the invoice verification, the invoice filed in the [[DMS]] for archiving. The invoice data is cross-checked with the order.
  - In case a corresponding [[Order]] is found, the order data is matched with the [[Invoice]] data and the invoice is approved and released for booking, if appropriate.
  - In case that no [[Order]] is available for the [[Invoice]], the invoice is passed on without an order reference, approved and released.
  Click the elements on the diagram to navigate to their description.
- SpecIF:Diagram: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
- SpecIF:Notation: BPMN Process Model

## Business Object: Invoice (SpecIF:View)
- dcterms:description: The following figure shows a detailed business data model of an [[Invoice]]. The business data model shows, that an invoice may have multiple invoice line items, both have a number of attributes.
- SpecIF:Diagram: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
- SpecIF:Notation: UML Class Diagram

## IT Architecture (SpecIF:Heading)
- dcterms:description: In this chapter, the IT architecture is documented.

## Application Landscape (SpecIF:View)
- dcterms:description: The application landscape shows the interfaces between the users such as [[Mail Room]] and the applications, which are needed to support the business processes, such as [[DMS]] or [[SAP FI]]. The business objects such as [[Electronic Document]] or [[Document Link]] are shown at the interfaces.
  Click the elements on the diagram to navigate to their description.
- SpecIF:Diagram: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
- SpecIF:Notation: FMC Block Diagram

## Function Tree (SpecIF:View)
- dcterms:description: The 'Function Tree' shows the hierarchical list of system modules down to system functions. In other words, it can be seen which system and subsystem offers a certain function.
  - A box contained in another signifies that it is a part of the outer box.
  - A function may be reused in Business Processes and so it can be seen which system functions support a given process ... or which processes require a given system function ... or which function is not being used, at all.
- SpecIF:Diagram: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
- SpecIF:Notation: FMC Block Diagram

## Requirements (SpecIF:Heading)
- dcterms:description: This is a listing of all requirements with its relations to elements of the system model. Of course, this is only an example and therefore not very many requirements are shown. In real world projects one would find a multi-level folder hierarchy with all the requirements covering the quality criteria as defined by ISO/IEC 9126.

## Functionality (SpecIF:Heading)
- dcterms:description: ISO/IEC 9126: Existence of a set of functions and their specified properties. The functions are those that satisfy stated or implied needs.
  - Suitability
  - Accuracy
  - Interoperability
  - Security
  - Functionality Compliance

## Security (SpecIF:Heading)

## Login requires authentication (IREB:Requirement)
- dcterms:identifier: Sec_005
- dcterms:description: Using the system requires login with appropriate credentials. The account is assigned certain privileges or roles by the user administrator.
  The method of authentication can vary. In its most simple form, a matching username/passowrd combination allows to use the application. In its most secure form, the user needs to pass the test of a biometric device such as a fingerprint reader. Authentication procedures to be supported are covered in separate requirements.
- SpecIF:LifecycleStatus: SpecIF:LifecycleStatusSubmitted
- SpecIF:Priority: SpecIF:priorityHigh
- ReqIF-WF.CustomerStatus: ReqIF-WF.CustomerStatus.ToEvaluate

## User authentication with username/password (IREB:Requirement)
- dcterms:identifier: Sec_006
- SpecIF:LifecycleStatus: SpecIF:LifecycleStatusSubmitted
- SpecIF:Priority: SpecIF:priorityHigh
- ReqIF-WF.SupplierStatus: ReqIF-WF.SupplierStatus.Agreed
- ReqIF-WF.CustomerStatus: ReqIF-WF.CustomerStatus.ToEvaluate

## User authentication via fingerprint reader (IREB:Requirement)
- dcterms:identifier: Sec_007
- SpecIF:LifecycleStatus: SpecIF:LifecycleStatusRejected
- SpecIF:Priority: SpecIF:priorityLow
- ReqIF-WF.SupplierStatus: ReqIF-WF.SupplierStatus.NotAgreed
- ReqIF-WF.CustomerStatus: ReqIF-WF.CustomerStatus.ToEvaluate

## Data access is protected according to a "CRUD" scheme (IREB:Requirement)
- dcterms:identifier: Sec_004
- dcterms:description: Access rights to a certain data entity control the complete lifecycle:
  - Create
  - Read
  - Update
  - Delete
- SpecIF:LifecycleStatus: SpecIF:LifecycleStatusSubmitted
- SpecIF:Priority: SpecIF:priorityMedium

## Data in storage is secure (IREB:Requirement)
- dcterms:identifier: Sec_001
- dcterms:description: All application data is encrypted for persistent storage - even the system administrator can not read it. This may be disabled for locally stored data in the system settings.
- SpecIF:LifecycleStatus: SpecIF:LifecycleStatusDrafted
- SpecIF:Priority: SpecIF:priorityHigh

## "Qualified" electronic signature (IREB:Requirement)
- dcterms:identifier: Sec_014
- dcterms:description: "Qualified" electronic signatures (Germany: "qualifizierte Signatur" §2 Nr.3 SigG) can be applied to a document. The signature ensures both authenticity of the sender and integrity of the document.
  Signatures can be delivered
  - as a separate file
  - in a common container
  - embedded (e.g. PDF or XML).
- SpecIF:LifecycleStatus: SpecIF:LifecycleStatusDrafted
- SpecIF:Priority: SpecIF:priorityLow

## Interoperability (SpecIF:Heading)
- dcterms:description: IEEE Glossary: The ability of two or more systems (or components) to exchange information and to use the information that has been exchanged.

## System monitoring via SNMP is supported (IREB:Requirement)
- dcterms:identifier: TeC_007
- dcterms:description: For system monitoring, the system is a SNMP agent supporting the GET, GETNEXT, GETBULK and TRAP operations.
- SpecIF:LifecycleStatus: SpecIF:LifecycleStatusDrafted

## Web-Services comply with SOAP architecture model (IREB:Requirement)
- dcterms:identifier: TeC_048
- SpecIF:LifecycleStatus: SpecIF:LifecycleStatusDrafted

## Web-Services conform to REST architecture model (IREB:Requirement)
- dcterms:identifier: TeC_049
- dcterms:description: Any object can be accessed via URI and HTTP-methods POST, GET, PUT, DELETE.
  There are some definitive advantages to REST when compared to SOAP, especially in operation and security.
  For example, have a look at: http://www.oio.de/public/xml/rest-webservices.htm
- SpecIF:LifecycleStatus: SpecIF:LifecycleStatusApproved

## Reliability (SpecIF:Heading)
- dcterms:description: ISO/IEC 9126: Capability to maintain its level of performance under stated conditions for a stated period of time.
  - Maturity
  - Fault Tolerance
  - Recoverability
  - Reliability Compliance

## Standard Data Availability (IREB:Requirement)
- dcterms:identifier: Rel_002
- dcterms:description: Standard availability as provided by the hardware platform is sufficient. The software application does not have any specific features to improve data availability. Thus, in case of a system failure, all data which has not been uploaded or backed-up, may be lost.
- SpecIF:LifecycleStatus: SpecIF:LifecycleStatusDrafted

## Client is autonomous (IREB:Requirement)
- dcterms:identifier: Rel_003
- dcterms:description: For client/server architectures: The client application works autonomously, i.e. without server support, for most operations.
  Of course, specific services such as package upload or backup are not available unless the server is online.
- SpecIF:LifecycleStatus: SpecIF:LifecycleStatusDrafted

## Recovery on electrical power outage (IREB:Requirement)
- dcterms:identifier: Rob_001
- dcterms:description: In case of electrical power outage, the system can recover on its own. To avoid inconsistent data, incomplete transactions are undone.
- SpecIF:LifecycleStatus: SpecIF:LifecycleStatusDrafted

## Usability (SpecIF:Heading)
- dcterms:description: ISO/IEC 9126: Effort needed for use, and on the individual assessment of such use, by a stated or implied set of users.
  - Understandability
  - Learnability
  - Operability
  - Attractiveness
  - Usability Compliance

## Learnability (SpecIF:Heading)

## Online help: Quick Intro (IREB:Requirement)
- dcterms:identifier: Doc_002
- dcterms:description: A brief introduction describing the major use-cases is made accessible after login.
- SpecIF:LifecycleStatus: SpecIF:LifecycleStatusSubmitted

## Online help is context-sensitive (IREB:Requirement)
- dcterms:identifier: Doc_001
- dcterms:description: Context-sensitive help is displayed when hovering the mouse over a dialog element.
- SpecIF:LifecycleStatus: SpecIF:LifecycleStatusApproved

## User manual (IREB:Requirement)
- dcterms:identifier: Doc_003
- dcterms:description: A user manual (Benutzer-Handbuch) for all user roles is provided.
- SpecIF:LifecycleStatus: SpecIF:LifecycleStatusDrafted

## Operability (SpecIF:Heading)

## System has logging facility (IREB:Requirement)
- dcterms:identifier: EoO_023
- dcterms:description: To allow for execution tracing, all functions (and processes) share a logging framework.
  - log entries show date-time-severity-category-messageID-message.
  - log entries can be redirected to console, pipe, file
  - severities are Debug, Information, Warning, Error, Fatal
  - log levels: runtime parameters configure log filters according to severity per category (name of originating plugin or module).
- SpecIF:LifecycleStatus: SpecIF:LifecycleStatusDrafted
- SpecIF:Priority: SpecIF:priorityHigh

## Remote login with application GUI is supported (IREB:Requirement)
- dcterms:identifier: EoO_015
- dcterms:description: Desktop sharing protocols can be used when explicitly enabled ("debug mode" or "remote training/assistance mode").
- SpecIF:LifecycleStatus: SpecIF:LifecycleStatusDrafted

## Attractiveness (SpecIF:Heading)

## System exhibits its purpose (IREB:Requirement)
- dcterms:identifier: UEx_003
- dcterms:description: While all underlying "mechanics" may be highly abstract, the face to the user is very concrete and indicates clearly its purpose. As a user I want to see immediate usefulness.
- SpecIF:LifecycleStatus: SpecIF:LifecycleStatusDrafted
- SpecIF:Priority: SpecIF:priorityHigh

## Skin is replaceable (IREB:Requirement)
- dcterms:identifier: UEx_005
- SpecIF:LifecycleStatus: SpecIF:LifecycleStatusDrafted
- SpecIF:Priority: SpecIF:priorityLow

## Application Window is resizeable (IREB:Requirement)
- dcterms:identifier: UEx_008
- dcterms:description: The display field under control of the application can be
  - full screen with total view
  - window with total view
  The size of the window panes is automatically adapted.
- SpecIF:LifecycleStatus: SpecIF:LifecycleStatusDrafted

## Efficiency (SpecIF:Heading)
- dcterms:description: ISO/IEC 9126: Relationship between the level of performance and the amount of resources used, under stated conditions.
  - Time Behaviour
  - Resource Utilisation
  - Efficiency Compliance

## Time Behavior (SpecIF:Heading)

## Data Volume of FileSystem (IREB:Requirement)
- dcterms:identifier: Per_001
- dcterms:description: Assumptions:
  - An average of 2 GB of files per patient.
  - 50 patients/operations per day will occupy 100GB of file space.
- SpecIF:LifecycleStatus: SpecIF:LifecycleStatusDrafted

## Number of concurrent users is < 1000 (IREB:Requirement)
- dcterms:identifier: Per_011
- dcterms:description: The maximum number of users which can be serviced without violating the maximum response times.
- SpecIF:LifecycleStatus: SpecIF:LifecycleStatusDrafted

## Maintainability (SpecIF:Heading)
- dcterms:description: ISO/IEC 9126: Effort needed to make specified modifications.
  - Analyzability
  - Changeability
  - Stability
  - Testability
  - Maintainability Compliance

## Semantic Versioning (IREB:Requirement)
- dcterms:identifier: REQ_147
- dcterms:description: http://tom.preston-werner.com: I propose a simple set of rules and requirements that dictate how version numbers are assigned and incremented. For this system to work, you first need to declare a public API. This may consist of documentation or be enforced by the code itself. Regardless, it is important that this API be clear and precise. Once you identify your public API, you communicate changes to it with specific increments to your version number. Consider a version format of X.Y.Z (Major.Minor.Patch). Bug fixes not affecting the API increment the patch version, backwards compatible API additions/changes increment the minor version, and backwards incompatible API changes increment the major version.
  For details see: http://semver.org
- SpecIF:LifecycleStatus: SpecIF:LifecycleStatusSubmitted

## Portability (SpecIF:Heading)
- dcterms:description: ISO/IEC 9126: Ability to be transferred from one environment to another.
  - Adaptability
  - Installability
  - Co-Existence
  - Replaceability
  - Portability Compliance

## Installability (SpecIF:Heading)

## MSI Installation package (IREB:Requirement)
- dcterms:identifier: EoO_011
- dcterms:description: Excecutable is delivered as an MSI installation package (for MS Windows).
- SpecIF:LifecycleStatus: SpecIF:LifecycleStatusDrafted

## RPM Installation package (IREB:Requirement)
- dcterms:identifier: EoO_012
- dcterms:description: Excecutable is delivered as an RPM installation package (for Linux).
- SpecIF:LifecycleStatus: SpecIF:LifecycleStatusDrafted

## Parts List (SpecIF:Heading)
- dcterms:description: This Parts List has been automatically generated from the model.

## Bank (FMC:Actor)

## Board of Directors (FMC:Actor)

## Finance Department (FMC:Actor)

## Controlling (FMC:Actor)

## Invoice Management (FMC:Actor)
- dcterms:description: Checks incoming [[Invoice]]s for completeness and correctness, based on [[Order]]s and accepted deliveries (goods or services).

## Approve Payment (FMC:Actor)

## Archive document (FMC:Actor)

## Assign Invoice Items to Accounts (FMC:Actor)

## Book Invoice (FMC:Actor)

## Check Acknowledgement of Receipt (FMC:Actor)
- dcterms:description: Check whether goods or services have been received in due quality.

## Invoice Delivered (FMC:Event)

## Invoice is Processed (FMC:Event)

## Match Invoice Items with Order (FMC:Actor)

## Match Invoice with Order (FMC:Actor)

## No Order found for Invoice (FMC:Event)

## Order found for Invoice (FMC:Event)

## Pass on Invoice without Order Reference (FMC:Actor)

## Scan documents (FMC:Actor)

## Postal Department (FMC:Actor)

## Mail Room (FMC:Actor)
- dcterms:description: Is responsible for the sorting of mail and its delivery to the offices.

## Address document to Department (FMC:Actor)
- dcterms:description: A notification e-mail will be sent by the [[DMS]]-System.

## Invoice Received (FMC:Event)

## Purchase Department (FMC:Actor)

## Supplier Management (FMC:Actor)
- dcterms:description: Is responsible for the management of [[supplier]]s and [[order]]s.

## Warehouse (FMC:Actor)

## DMS (FMC:Actor)
- dcterms:description: Document Management System, which is used for the administration of documents in the [[Document Archive]].

## Document Archive (FMC:State)

## Invoice (FMC:State)
- dcterms:description: An invoice is a document which contains a detailed list of the monetary claim of a supplier for delivered goods or services. It contains all required data for the administration of invoices.

## Date (FMC:State)

## Invoice Final Value (FMC:State)

## Invoice Line Item (FMC:State)

## Article ID (FMC:State)

## Article Name (FMC:State)

## Count (FMC:State)

## Unit Price (FMC:State)

## Invoice Number (FMC:State)

## Net Value (FMC:State)

## Order Number (FMC:State)

## Performance Date / Delivery Date (FMC:State)

## Supplier Name (FMC:State)

## Terms of Payment (FMC:State)

## VAT-Value (FMC:State)

## Document Link (FMC:State)

## Document Scanner (FMC:Actor)
- dcterms:description: Scanning system, which is used for the converting of paper documents into electronic documents.

## e-mail (FMC:State)

## Electronic Document (FMC:State)

## Invoice Document (FMC:State)

## Money Transfer (FMC:State)

## Payment Order (FMC:State)
- dcterms:description: Is an instruction to the house bank to execute the payment to the specified recipient.

## Payment Receipt (FMC:State)
- dcterms:description: Is the confirmation of payment on an account which is issued by the house bank.

## Process Received Invoices (FMC:Actor)
- dcterms:description: Is responsible for the processing of the incoming [[invoice]]s.

## SAP Systems (FMC:Actor)

## Master Data Management (FMC:State)

## Accepted Deliveries (FMC:State)
- dcterms:description: Goods or Services.

## Order (FMC:State)
- dcterms:description: Is an instruction to the supplier to deliver a specified list of articles on a specified date to a specified address. All data necessary for the administration of the order are collected.

## Supplier (FMC:State)
- dcterms:description: All data for the administration of suppliers are collected.

## SAP FI (FMC:Actor)
- dcterms:description: SAP Financial Accounting System, which is used for the administration of [[invoice]]s and cash flow among others.

## SAP SCM (FMC:Actor)
- dcterms:description: SAP Supply Chain Management System, which is used for the administration of [[supplier]] data and [[order]]s.

## Supplier (FMC:Actor)

## Model Elements (Glossary) (SpecIF:Heading)
- dcterms:type: SpecIF:Glossary

## Statements
- Organization Chart SpecIF:shows Board of Directors
- Organization Chart SpecIF:shows Controlling
- Organization Chart SpecIF:shows Finance Department
- Organization Chart SpecIF:shows Invoice Management
- Organization Chart SpecIF:shows Postal Department
- Organization Chart SpecIF:shows Mail Room
- Organization Chart SpecIF:shows Purchase Department
- Organization Chart SpecIF:shows Supplier Management
- Organization Chart SpecIF:shows Warehouse
- Business Landscape SpecIF:shows Bank
- Business Landscape SpecIF:shows Invoice
- Business Landscape SpecIF:shows Invoice Management
- Business Landscape SpecIF:shows Mail Room
- Business Landscape SpecIF:shows Order
- Business Landscape SpecIF:shows Payment Order
- Business Landscape SpecIF:shows Payment Receipt
- Business Landscape SpecIF:shows Supplier
- Business Landscape SpecIF:shows Supplier
- Business Landscape SpecIF:shows Supplier Management
- Process: Invoice Receipt Processing SpecIF:shows Accepted Deliveries
- Process: Invoice Receipt Processing SpecIF:shows Address document to Department
- Process: Invoice Receipt Processing SpecIF:shows Archive document
- Process: Invoice Receipt Processing SpecIF:shows Approve Payment
- Process: Invoice Receipt Processing SpecIF:shows Assign Invoice Items to Accounts
- Process: Invoice Receipt Processing SpecIF:shows Book Invoice
- Process: Invoice Receipt Processing SpecIF:shows Check Acknowledgement of Receipt
- Process: Invoice Receipt Processing SpecIF:shows Invoice Delivered
- Process: Invoice Receipt Processing SpecIF:shows Invoice Document
- Process: Invoice Receipt Processing SpecIF:shows Invoice is Processed
- Process: Invoice Receipt Processing SpecIF:shows Invoice Management
- Process: Invoice Receipt Processing SpecIF:shows Invoice Received
- Process: Invoice Receipt Processing SpecIF:shows Mail Room
- Process: Invoice Receipt Processing SpecIF:shows Match Invoice Items with Order
- Process: Invoice Receipt Processing SpecIF:shows Match Invoice with Order
- Process: Invoice Receipt Processing SpecIF:shows Money Transfer
- Process: Invoice Receipt Processing SpecIF:shows No Order found for Invoice
- Process: Invoice Receipt Processing SpecIF:shows Order found for Invoice
- Process: Invoice Receipt Processing SpecIF:shows Pass on Invoice without Order Reference
- Process: Invoice Receipt Processing SpecIF:shows Process Received Invoices
- Process: Invoice Receipt Processing SpecIF:shows Scan documents
- Business Object: Invoice SpecIF:shows Article ID
- Business Object: Invoice SpecIF:shows Count
- Business Object: Invoice SpecIF:shows Article Name
- Business Object: Invoice SpecIF:shows Date
- Business Object: Invoice SpecIF:shows Invoice Final Value
- Business Object: Invoice SpecIF:shows Invoice
- Business Object: Invoice SpecIF:shows Invoice Line Item
- Business Object: Invoice SpecIF:shows Invoice Number
- Business Object: Invoice SpecIF:shows Net Value
- Business Object: Invoice SpecIF:shows Order Number
- Business Object: Invoice SpecIF:shows Performance Date / Delivery Date
- Business Object: Invoice SpecIF:shows Supplier Name
- Business Object: Invoice SpecIF:shows Terms of Payment
- Business Object: Invoice SpecIF:shows Unit Price
- Business Object: Invoice SpecIF:shows VAT-Value
- Application Landscape SpecIF:shows Accepted Deliveries
- Application Landscape SpecIF:shows DMS
- Application Landscape SpecIF:shows Document Archive
- Application Landscape SpecIF:shows Document Link
- Application Landscape SpecIF:shows e-mail
- Application Landscape SpecIF:shows Document Scanner
- Application Landscape SpecIF:shows Electronic Document
- Application Landscape SpecIF:shows Invoice
- Application Landscape SpecIF:shows Invoice Document
- Application Landscape SpecIF:shows Invoice Management
- Application Landscape SpecIF:shows Mail Room
- Application Landscape SpecIF:shows Master Data Management
- Application Landscape SpecIF:shows SAP FI
- Application Landscape SpecIF:shows Order
- Application Landscape SpecIF:shows SAP SCM
- Application Landscape SpecIF:shows SAP Systems
- Application Landscape SpecIF:shows Supplier
- Application Landscape SpecIF:shows Warehouse
- Function Tree SpecIF:shows Approve Payment
- Function Tree SpecIF:shows Assign Invoice Items to Accounts
- Function Tree SpecIF:shows Book Invoice
- Function Tree SpecIF:shows Check Acknowledgement of Receipt
- Function Tree SpecIF:shows Match Invoice Items with Order
- Function Tree SpecIF:shows Match Invoice with Order
- Function Tree SpecIF:shows SAP FI
- Function Tree SpecIF:shows SAP SCM
- Function Tree SpecIF:shows SAP Systems
- DMS oslc_rm:satisfies Login requires authentication
- SAP FI oslc_rm:satisfies Login requires authentication
- Login requires authentication SpecIF:dependsOn User authentication with username/password
- SAP SCM oslc_rm:satisfies Login requires authentication
- Login requires authentication SpecIF:dependsOn User authentication via fingerprint reader
- SAP FI oslc_rm:satisfies User authentication with username/password
- SAP SCM oslc_rm:satisfies User authentication with username/password
- SAP FI oslc_rm:satisfies User authentication via fingerprint reader
- SAP SCM oslc_rm:satisfies User authentication via fingerprint reader
- Document Archive oslc_rm:satisfies Data access is protected according to a "CRUD" scheme
- Master Data Management oslc_rm:satisfies Data access is protected according to a "CRUD" scheme
- Document Archive oslc_rm:satisfies Data in storage is secure
- Master Data Management oslc_rm:satisfies Data in storage is secure
- DMS oslc_rm:satisfies System monitoring via SNMP is supported
- SAP Systems oslc_rm:satisfies System monitoring via SNMP is supported
- DMS oslc_rm:satisfies Web-Services conform to REST architecture model
- DMS oslc_rm:satisfies Client is autonomous
- SAP Systems oslc_rm:satisfies Recovery on electrical power outage
- DMS oslc_rm:satisfies Online help: Quick Intro
- SAP Systems oslc_rm:satisfies Online help: Quick Intro
- Approve Payment oslc_rm:satisfies Online help is context-sensitive
- Assign Invoice Items to Accounts oslc_rm:satisfies Online help is context-sensitive
- Book Invoice oslc_rm:satisfies Online help is context-sensitive
- Check Acknowledgement of Receipt oslc_rm:satisfies Online help is context-sensitive
- Match Invoice Items with Order oslc_rm:satisfies Online help is context-sensitive
- Match Invoice with Order oslc_rm:satisfies Online help is context-sensitive
- SAP Systems oslc_rm:satisfies System has logging facility
- SAP Systems oslc_rm:satisfies System exhibits its purpose
- SAP Systems oslc_rm:satisfies Skin is replaceable
- SAP Systems oslc_rm:satisfies Application Window is resizeable
- SAP Systems oslc_rm:satisfies Number of concurrent users is < 1000
- DMS oslc_rm:satisfies Semantic Versioning
- Document Scanner oslc_rm:satisfies Semantic Versioning
- SAP Systems oslc_rm:satisfies Semantic Versioning
- DMS oslc_rm:satisfies MSI Installation package
- Document Scanner oslc_rm:satisfies MSI Installation package
- SAP Systems oslc_rm:satisfies MSI Installation package
- DMS oslc_rm:satisfies RPM Installation package
- Document Scanner oslc_rm:satisfies RPM Installation package
- SAP Systems oslc_rm:satisfies RPM Installation package
- Archive document SpecIF:precedes Address document to Department
- Invoice Received SpecIF:precedes Address document to Department
- Address document to Department SpecIF:precedes Invoice Delivered
- Mail Room SpecIF:contains Address document to Department
- Process Received Invoices SpecIF:contains Address document to Department
- Approve Payment SpecIF:writes Money Transfer
- Approve Payment SpecIF:reads Money Transfer
- Check Acknowledgement of Receipt SpecIF:precedes Approve Payment
- Approve Payment SpecIF:precedes Book Invoice
- Invoice Management SpecIF:contains Approve Payment
- Process Received Invoices SpecIF:contains Approve Payment
- SAP FI SpecIF:contains Approve Payment
- Scan documents SpecIF:precedes Archive document
- Invoice Management SpecIF:contains Archive document
- Mail Room SpecIF:contains Archive document
- Archive document SpecIF:precedes Match Invoice with Order
- Process Received Invoices SpecIF:contains Archive document
- Match Invoice Items with Order SpecIF:precedes Assign Invoice Items to Accounts
- Assign Invoice Items to Accounts SpecIF:precedes Check Acknowledgement of Receipt
- Invoice Management SpecIF:contains Assign Invoice Items to Accounts
- Process Received Invoices SpecIF:contains Assign Invoice Items to Accounts
- SAP FI SpecIF:contains Assign Invoice Items to Accounts
- Bank SpecIF:writes Payment Receipt
- Bank SpecIF:reads Payment Order
- Board of Directors SpecIF:contains Finance Department
- Board of Directors SpecIF:contains Postal Department
- Board of Directors SpecIF:contains Purchase Department
- Check Acknowledgement of Receipt SpecIF:precedes Book Invoice
- Book Invoice SpecIF:precedes Invoice is Processed
- Invoice Management SpecIF:contains Book Invoice
- Process Received Invoices SpecIF:contains Book Invoice
- SAP FI SpecIF:contains Book Invoice
- Check Acknowledgement of Receipt SpecIF:writes Accepted Deliveries
- Check Acknowledgement of Receipt SpecIF:reads Accepted Deliveries
- Pass on Invoice without Order Reference SpecIF:precedes Check Acknowledgement of Receipt
- Invoice Management SpecIF:contains Check Acknowledgement of Receipt
- Process Received Invoices SpecIF:contains Check Acknowledgement of Receipt
- SAP FI SpecIF:contains Check Acknowledgement of Receipt
- Finance Department SpecIF:contains Controlling
- DMS SpecIF:writes Document Archive
- DMS SpecIF:reads Document Archive
- DMS SpecIF:writes Document Link
- DMS SpecIF:writes e-mail
- DMS SpecIF:reads Electronic Document
- Document Scanner SpecIF:reads Invoice Document
- Document Scanner SpecIF:writes Electronic Document
- Finance Department SpecIF:contains Invoice Management
- Invoice Management SpecIF:contains Invoice Delivered
- Invoice Management SpecIF:contains Invoice is Processed
- Invoice Management SpecIF:contains Match Invoice with Order
- Invoice Management SpecIF:contains Match Invoice Items with Order
- Invoice Management SpecIF:contains No Order found for Invoice
- Invoice Management SpecIF:contains Order found for Invoice
- Invoice Management SpecIF:contains Pass on Invoice without Order Reference
- Invoice Management SpecIF:contains Scan documents
- Invoice Management SpecIF:writes Invoice
- Invoice Management SpecIF:reads Invoice
- Invoice Management SpecIF:writes Payment Order
- Invoice Management SpecIF:reads e-mail
- Invoice Management SpecIF:reads Order
- Invoice Management SpecIF:reads Payment Receipt
- Invoice Management SpecIF:reads Supplier
- SAP FI FMC:sendsTo Invoice Management
- SAP SCM FMC:sendsTo Invoice Management
- Mail Room FMC:sendsTo Invoice Management
- Invoice Management FMC:sendsTo SAP FI
- Invoice Management FMC:sendsTo SAP SCM
- Mail Room SpecIF:contains Invoice Received
- Mail Room SpecIF:contains Invoice Delivered
- Mail Room SpecIF:contains Scan documents
- Mail Room SpecIF:writes Invoice Document
- Mail Room SpecIF:reads Invoice
- Postal Department SpecIF:contains Mail Room
- Order found for Invoice SpecIF:precedes Match Invoice Items with Order
- Process Received Invoices SpecIF:contains Match Invoice Items with Order
- SAP FI SpecIF:contains Match Invoice Items with Order
- Invoice Delivered SpecIF:precedes Match Invoice with Order
- Match Invoice with Order SpecIF:precedes No Order found for Invoice
- Match Invoice with Order SpecIF:precedes Order found for Invoice
- Process Received Invoices SpecIF:contains Match Invoice with Order
- SAP FI SpecIF:contains Match Invoice with Order
- No Order found for Invoice SpecIF:precedes Pass on Invoice without Order Reference
- Process Received Invoices SpecIF:contains Pass on Invoice without Order Reference
- Process Received Invoices SpecIF:contains Invoice Delivered
- Process Received Invoices SpecIF:contains No Order found for Invoice
- Process Received Invoices SpecIF:contains Order found for Invoice
- Process Received Invoices SpecIF:contains Scan documents
- Purchase Department SpecIF:contains Supplier Management
- Purchase Department SpecIF:contains Warehouse
- SAP FI SpecIF:writes Master Data Management
- SAP FI SpecIF:reads Master Data Management
- SAP FI SpecIF:reads Document Link
- SAP Systems SpecIF:contains SAP FI
- SAP SCM SpecIF:writes Master Data Management
- SAP SCM SpecIF:reads Master Data Management
- Warehouse FMC:sendsTo SAP SCM
- SAP Systems SpecIF:contains SAP SCM
- SAP SCM FMC:sendsTo Warehouse
- SAP Systems SpecIF:contains Master Data Management
- Scan documents SpecIF:writes Invoice Document
- Scan documents SpecIF:reads Invoice Document
- Invoice Delivered SpecIF:precedes Scan documents
- Invoice Received SpecIF:precedes Scan documents
- Supplier SpecIF:writes Invoice
- Supplier SpecIF:reads Order
- Supplier Management SpecIF:reads Order
- Supplier Management SpecIF:writes Order
- Supplier Management SpecIF:writes Supplier
- Supplier Management SpecIF:reads Supplier
- Master Data Management SpecIF:contains Accepted Deliveries
- Invoice Line Item SpecIF:contains Article ID
- Invoice Line Item SpecIF:contains Article Name
- Invoice Line Item SpecIF:contains Count
- Invoice SpecIF:contains Date
- Document Archive SpecIF:contains Invoice
- Invoice SpecIF:contains Invoice Final Value
- Invoice SpecIF:contains Invoice Line Item
- Invoice SpecIF:contains Invoice Number
- Invoice SpecIF:contains Net Value
- Invoice SpecIF:contains Order Number
- Invoice SpecIF:contains Performance Date / Delivery Date
- Invoice SpecIF:contains Supplier Name
- Invoice SpecIF:contains Terms of Payment
- Invoice SpecIF:contains VAT-Value
- Master Data Management SpecIF:contains Invoice
- Invoice Line Item SpecIF:contains Unit Price
- Master Data Management SpecIF:contains Order
- Master Data Management SpecIF:contains Supplier
